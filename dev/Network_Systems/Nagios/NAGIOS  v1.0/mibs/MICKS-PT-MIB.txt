MICKS-PT-MIB DEFINITIONS ::= BEGIN

    IMPORTS
        enterprises
            FROM MICKS-BASIC-SMI;

    pt			OBJECT IDENTIFIER ::= { enterprises 7933 }
    ptprod		OBJECT IDENTIFIER ::= { pt 1 }
    raidv4		OBJECT IDENTIFIER ::= { ptprod 20 }

    raidv4System	OBJECT IDENTIFIER ::= { raidv4 1 }
    raidv4Storage	OBJECT IDENTIFIER ::= { raidv4 2 }


    -- raidv4ControllerTable (enterprises.7933.1.3)
    raidv4ControllerTable	OBJECT IDENTIFIER ::=  { raidv4System  3 }

    raidv4ControllerEntry	OBJECT IDENTIFIER ::=  { raidv4ControllerTable 1 }

     raidv4CtrlNumOfPhyDrvOffline		OBJECT-TYPE
        SYNTAX		Integer32
        MAX-ACCESS	read-only
        STATUS		current
        DESCRIPTION	"The number of unconfigured physical drive(s) in the Controller."
        ::=  {  raidv4ControllerEntry  21  }
    rNoPdOff		OBJECT IDENTIFIER ::= { raidv4CtrlNumOfPhyDrvOffline  1 }

     raidv4CtrlNumOfPhyDrvWithPFA		OBJECT-TYPE
        SYNTAX		Integer32
        MAX-ACCESS	read-only
        STATUS		current
        DESCRIPTION	"The number of unconfigured physical drive(s) in the Controller."
        ::=  {  raidv4ControllerEntry  22  }
    rNoPdPFA		OBJECT IDENTIFIER ::= { raidv4CtrlNumOfPhyDrvWithPFA  1 }

     raidv4CtrlNumOfPhyDrvRebuilding		OBJECT-TYPE
        SYNTAX		Integer32
        MAX-ACCESS	read-only
        STATUS		current
        DESCRIPTION	"The number of unconfigured physical drive(s) in the Controller."
        ::=  {  raidv4ControllerEntry  23  }
    rNoPdReb		OBJECT IDENTIFIER ::= { raidv4CtrlNumOfPhyDrvRebuilding  1 }

     raidv4CtrlNumOfPhyDrvMissing		OBJECT-TYPE
        SYNTAX		Integer32
        MAX-ACCESS	read-only
        STATUS		current
        DESCRIPTION	"The number of unconfigured physical drive(s) in the Controller."
        ::=  {  raidv4ControllerEntry  24  }
    rNoPdMis		OBJECT IDENTIFIER ::= { raidv4CtrlNumOfPhyDrvMissing  1 }

     raidv4CtrlNumOfPhyDrvUnconfigured		OBJECT-TYPE
        SYNTAX		Integer32
        MAX-ACCESS	read-only
        STATUS		current
        DESCRIPTION	"The number of unconfigured physical drive(s) in the Controller."
        ::=  {  raidv4ControllerEntry  25  }
    rNoPdUnc		OBJECT IDENTIFIER ::= { raidv4CtrlNumOfPhyDrvUnconfigured  1 }

    raidv4CtrlNumOfLogDrvOffline		OBJECT-TYPE
        SYNTAX		Integer32
        MAX-ACCESS	read-only
        STATUS		current
        DESCRIPTION	"The number of offline logical drive(s) in the controller."
        ::=  {  raidv4ControllerEntry  28  }
    rNoLdOff		OBJECT IDENTIFIER ::= { raidv4CtrlNumOfLogDrvOffline  1 }

     raidv4CtrlNumOfLogDrvDegraded		OBJECT-TYPE
        SYNTAX		Integer32
        MAX-ACCESS	read-only
        STATUS		current
        DESCRIPTION	"The number of degraded logical drive(s) in the controller."
        ::=  {  raidv4ControllerEntry  64  }
    rNoLdDeg		OBJECT IDENTIFIER ::= { raidv4CtrlNumOfLogDrvDegraded  1 }


    -- raidv4PhyDrvTable (enterprises.7933.2.1)
    raidv4PhyDrvTable	OBJECT IDENTIFIER ::= { raidv4Storage 1 }

    raidv4PhyDrvEntry	OBJECT IDENTIFIER ::= { raidv4PhyDrvTable 1 }

    raidv4PhydrvOperationalStatus		OBJECT-TYPE
        SYNTAX		DisplayString
        MAX-ACCESS	read-only
        STATUS		current
        DESCRIPTION	"The operational status of the physical drive."
        ::=  {  raidv4PhyDrvEntry  8  }
    rPdOpStat		OBJECT IDENTIFIER ::= { raidv4PhydrvOperationalStatus  1 }

    END
