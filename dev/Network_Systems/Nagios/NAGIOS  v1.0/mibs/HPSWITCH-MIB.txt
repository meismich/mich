-- =================================================================
--
--     $Workfile::   hpswitch.mib                                  $ 
--     $Revision: /main/1 $
--      $Modtime::   19 Oct 1993 14:23:26                          $
--         $Date: 1996/05/09 17:05 UTC $ 
--       $Author: dja $
--      $Archive::   I:/software/pvcs/1500x/ip/snmp/agent/hpswitch.$
--
-- =================================================================

HPSWITCH-MIB DEFINITIONS ::= BEGIN

-- Kalpana Base Release 1.0

-- Copyright 1992 Kalpana.  All rights reserved.

-- This SNMP Management Information Specification (Specification)
-- embodies Kalpana's confidential and proprietary
-- intellectual property.  Kalpana retains all title
-- and ownership in the Specification including any revisions.

-- This Specification is supplied "AS IS", and Kalpana
-- makes no warranty, either expressed or implied, as to the use,
-- operation, condition, or performance of the Specification.


IMPORTS
	TimeTicks, IpAddress, Counter
			FROM RFC1155-SMI
	OBJECT-TYPE
			FROM RFC-1212
	DisplayString
			FROM RFC1213-MIB
	enterprises	FROM RFC1155-SMI;

-- Ethernet station MAC address
MacAddr ::= OCTET STRING (SIZE(6))

hp		OBJECT IDENTIFIER ::= { enterprises 11 }

--Entry for "nm"
nm		OBJECT IDENTIFIER ::= { hp 2 }

--Entry for "icf"
icf		OBJECT IDENTIFIER ::= { nm 14 }

--Entry for "icfEswitch"
icfEswitch	OBJECT IDENTIFIER ::= { icf 6 }

-- EtherSwitch objects
hpEs		OBJECT IDENTIFIER ::= { icfEswitch 1 }


-- Global objects for the EtherSwitch

hpEsMain	OBJECT IDENTIFIER ::= { hpEs 1 }

-- Configuration objects
hpEsConfig	OBJECT IDENTIFIER ::= { hpEsMain 1 }

hpEsFwVer OBJECT-TYPE
	SYNTAX	DisplayString
	ACCESS	read-only
	STATUS	mandatory
	DESCRIPTION
		"The firmware version in the form major.minor."
	::= { hpEsConfig 1 }

hpEsHwVer OBJECT-TYPE
	SYNTAX	DisplayString
	ACCESS	read-only
	STATUS	mandatory
	DESCRIPTION
		"The hardware version in the form major.minor."
	::= { hpEsConfig 2 }

hpEsIpAddr OBJECT-TYPE
	SYNTAX	IpAddress
	ACCESS	read-write
	STATUS	mandatory
	DESCRIPTION
		"The administrative value of the IP address.  The
		current operational IP address can be obtained by
		the ipAdEntAddr entry in the ipAddrTable.

		This parameter will take effect only after a reset
		(hpEsReset) is issued or a power cycle."
	::= { hpEsConfig 3 }

hpEsNetMask OBJECT-TYPE
	SYNTAX	IpAddress
	ACCESS	read-write
	STATUS	mandatory
	DESCRIPTION
		"The administrative value of the subnet mask.  The
		current operational subnet mask can be obtained by
		the ipAdEntNetMask entry in the ipAddrTable.

		This parameter will take effect only after a reset
		(hpEsReset) is issued or a power cycle."
	::= { hpEsConfig 4 }

hpEsDefaultGateway OBJECT-TYPE
	SYNTAX	IpAddress
	ACCESS	read-write
	STATUS	mandatory
	DESCRIPTION
		"The administrative value of the default gateway
		(router) IP address.  The current operational
		default gateway's IP address can be obtained from
		the ipRouteTable.

		This parameter will take effect only after a reset
		(hpEsReset) is issued or a power cycle."
	::= { hpEsConfig 5 }

hpEsTrapRcvrMaxEnt OBJECT-TYPE
	SYNTAX	INTEGER
	ACCESS	read-only
	STATUS	mandatory
	DESCRIPTION
		"The maximum number of rows in the trap receiver
		table."
	::= { hpEsConfig 6 }

hpEsTrapRcvrCurEnt OBJECT-TYPE
	SYNTAX	INTEGER
	ACCESS	read-only
	STATUS	mandatory
	DESCRIPTION
		"The current number of rows in the trap receiver
		table."
	::= { hpEsConfig 7 }

hpEsTrapRcvrNext OBJECT-TYPE
	SYNTAX	INTEGER (0..655535)
	ACCESS	read-only
	STATUS	mandatory
	DESCRIPTION
		"The index of the next available row to be created
		in the trap receiver table.  A value of zero means
		that the table is full and no more rows can be
		added."
	::= { hpEsConfig 8 }

hpEsTrapRcvrTable OBJECT-TYPE
	SYNTAX	SEQUENCE OF HpEsTrapRcvrEntry
	ACCESS	not-accessible
	STATUS	mandatory
	DESCRIPTION
		"A table of managers to which to send traps.
		Entries in the table are saved across resets and
		power cycles."
	::= { hpEsConfig 9 }

hpEsTrapRcvrEntry OBJECT-TYPE
	SYNTAX	HpEsTrapRcvrEntry
	ACCESS	not-accessible
	STATUS	mandatory
	DESCRIPTION
		"Definition of rows in the trap receiver table.
		The column hpEsTrapRcvrStatus is used to create
		and delete rows in the table.  Creation requires
		a SET PDU with objects hpEsTrapRcvrStatus,
		hpEsTrapRcvrIpAddress, and hpEsTrapRcvrComm."
	INDEX	{ hpEsTrapRcvrIndex }
	::= { hpEsTrapRcvrTable 1 }

HpEsTrapRcvrEntry ::= SEQUENCE {
	hpEsTrapRcvrIndex	INTEGER,
	hpEsTrapRcvrStatus	INTEGER,
	hpEsTrapRcvrIpAddress	IpAddress,
	hpEsTrapRcvrComm	DisplayString
	}

hpEsTrapRcvrIndex OBJECT-TYPE
	SYNTAX	INTEGER (1..65535)
	ACCESS	read-only
	STATUS	mandatory
	DESCRIPTION
		"The index of the row in the table."
	::= { hpEsTrapRcvrEntry 1 }

hpEsTrapRcvrStatus OBJECT-TYPE
	SYNTAX	INTEGER {
		other(1),	-- none of the following
		valid(2),	-- a valid address
		invalid(3),	-- an invalid address
		create(4)	-- create row
		}
	ACCESS	read-write
	STATUS	mandatory
	DESCRIPTION
		"Setting this object to the value invalid(3)
		deletes the row from the table.  The value
		invalid(3) should never be returned on a GET.  The
		value of create(4) on a SET causes a new row to be
		created if the row does not already exist.  If it
		does, then a 'badValue'error should be returned.
		The value returned on GETs should be valid(2) or
		other(1), which is used to indicate any other
		condition."
	::= { hpEsTrapRcvrEntry 2 }

hpEsTrapRcvrIpAddress OBJECT-TYPE
	SYNTAX	IpAddress
	ACCESS	read-write
	STATUS	mandatory
	DESCRIPTION
		"IP address for an SNMP manager that is to receive
		the trap."
	::= { hpEsTrapRcvrEntry 3 }

hpEsTrapRcvrComm OBJECT-TYPE
	SYNTAX	DisplayString
	ACCESS	read-write
	STATUS	mandatory
	DESCRIPTION
		"Community string to use."
	::= { hpEsTrapRcvrEntry 4 }


-- System Module objects
hpEsSys	OBJECT IDENTIFIER ::= { hpEsMain 2 }


hpEsNumPorts OBJECT-TYPE
	SYNTAX	INTEGER
	ACCESS	read-only
	STATUS	mandatory
	DESCRIPTION
		"The maximum number of ports on the switch."
	::= { hpEsSys 1 }

hpEsNumStations OBJECT-TYPE
	SYNTAX	INTEGER
	ACCESS	read-only
	STATUS	mandatory
	DESCRIPTION
		"Aggregate number of currently active stations
		(nodes) on all ports on the switch.  This is the
		value from the system module."
	::= { hpEsSys 2 }

hpEsMostStations OBJECT-TYPE
	SYNTAX	INTEGER
	ACCESS	read-only
	STATUS	mandatory
	DESCRIPTION
		"Highest aggregate number of stations ever active
		on all ports at one time, since the last reset or
		power cycle.  This is the value as seen by the
		system module."
	::= { hpEsSys 3 }

hpEsMaxStations OBJECT-TYPE
	SYNTAX	INTEGER
	ACCESS	read-only
	STATUS	mandatory
	DESCRIPTION
		"Highest aggregate number of stations which the
		switch can support simultaneously.  (This is the
		maximum number that the system module can
		support.)"
	::= { hpEsSys 4 }

hpEsReset OBJECT-TYPE
	SYNTAX	INTEGER {
		other(1),	-- none of the following
		running(2),	-- switch is running
		softReset(3),	-- do soft reset of switch
		hardReset(4)	-- do hard reset of switch
		}
	ACCESS	read-write
	STATUS	mandatory
	DESCRIPTION
		"This object is used to reset the switch.  Writing
		softReset(3) causes the switch to reset the
		hardware, run quick diagnostics, clear all
		counters, start switching, issue a warmstart trap,
		and then be able to respond to SNMP requests.
		Writing hardReset(4) causes the switch to run
		power up diagnostics and then execute a soft
		reset.	Note:  all address tables are cleared in
		both cases.  The administrative parameters from
		nonvolatile memory are used to initialize the
		operational parameters.  The value returned on GETs 
		should be running(2) or other(1), which is used to
		indicate any other condition."
	::= { hpEsSys 5 }

hpEsNumResets OBJECT-TYPE
	SYNTAX	Counter
	ACCESS	read-only
	STATUS	mandatory
	DESCRIPTION
		"Number of soft resets the switch has executed
		since the last hard reset or power cycle.  Soft
		resets are defined as writing softReset(3) to
		hpEsReset, pressing the front panel reset button,
		executing a soft reset from the console, or resets
		induced by the switch firmware."
	::= { hpEsSys 6 }

hpEsAddrAgingTime OBJECT-TYPE
	SYNTAX	INTEGER (0..9999)
	ACCESS	read-write
	STATUS	mandatory
	DESCRIPTION
		"Number of minutes of inactivity before an address
		entity is aged out.  A value of zero means no
		aging.	Note:  if an address shows up on another
		port, the original port to address assignment is
		automatically deleted.  The value is saved across
		resets and power cycles."
	::= { hpEsSys 7 }

hpEsSysStaTable OBJECT-TYPE
	SYNTAX	SEQUENCE OF HpEsSysStaEntry
	ACCESS	not-accessible
	STATUS	mandatory
	DESCRIPTION
		"A table of station addresses from all ports known
		to the system module."
	::= { hpEsSys 9 }

hpEsSysStaEntry OBJECT-TYPE
	SYNTAX	HpEsSysStaEntry
	ACCESS	not-accessible
	STATUS	mandatory
	DESCRIPTION
		"Definition of the rows in the system module
		station address table.	Rows can not be created or
		deleted via SNMP requests."
	INDEX	{ hpEsSysStaMacAddr }
	::= { hpEsSysStaTable 1 }

HpEsSysStaEntry ::= SEQUENCE {
	hpEsSysStaMacAddr	OCTET STRING (SIZE(6)),
	hpEsSysStaPort 	INTEGER,
	hpEsSysStaTraffic	OCTET STRING
	}

hpEsSysStaMacAddr OBJECT-TYPE
	SYNTAX	OCTET STRING (SIZE(6))
	ACCESS	read-only
	STATUS	mandatory
	DESCRIPTION
		"The Station's MAC address."
	::= { hpEsSysStaEntry 1 }

hpEsSysStaPort OBJECT-TYPE
	SYNTAX	INTEGER
	ACCESS	read-only
	STATUS	mandatory
	DESCRIPTION
		"The source port for the Station."
	::= { hpEsSysStaEntry 2 }

hpEsSysStaTraffic OBJECT-TYPE
	SYNTAX	OCTET STRING
	ACCESS	read-only
	STATUS	mandatory
	DESCRIPTION
		"A bit string that identifies with value of one of
		the ports that this station has generated traffic
		to or from.  The bits are numbered starting at zero,
		with bit zero being the high order bit in the first
		byte, bit seven being the low order bit in the first
		byte, bit eight being the high order bit in the second
		byte, etc.  Ports correspond with bits (i.e., port 1 is
		bit 1, etc.).	The size of this in octets is the number
		of ports (i.e., hpEsNumPorts), divided by 8, plus
		one."
	::= { hpEsSysStaEntry 3 }

-- Topology information

hpEsTop	OBJECT IDENTIFIER ::= { hpEs 2 }


-- Port level objects

hpEsPort	OBJECT IDENTIFIER ::= { hpEs 3 }


-- EtherSwitch Port table

hpEsPortTable OBJECT-TYPE
	SYNTAX	SEQUENCE OF HpEsPortEntry
	ACCESS	not-accessible
	STATUS	mandatory
	DESCRIPTION
		"A table of information about each port.  The
		number of rows is given by hpEsNumPorts."
	::= { hpEsPort 1 }

hpEsPortEntry OBJECT-TYPE
	SYNTAX	HpEsPortEntry
	ACCESS	not-accessible
	STATUS	mandatory
	DESCRIPTION
		"Definition of rows in the port table.  The number
		of rows is determined by the hardware and is
		specified by the value of hpEsNumPorts.  Rows can
		not be created or deleted via SNMP requests."
	INDEX { hpEsPortIndex }
	::= { hpEsPortTable 1 }

HpEsPortEntry ::= SEQUENCE {
	hpEsPortIndex		INTEGER,
	hpEsPortOprStatus	INTEGER,
	hpEsPortExtConn	INTEGER,
	hpEsPortDuplex 	INTEGER,
	hpEsPortRcvLocalFrames Counter,
	hpEsPortForwardedFrames Counter,
	hpEsPortMostStations	Counter,
	hpEsPortMaxStations	Counter,
	hpEsPortSWHandledFrames Counter,
	hpEsPortLocalStations	Counter,
	hpEsPortRemoteStations Counter,
	hpEsPortUnknownStaFrames Counter,
	hpEsPortResetStats	INTEGER,
	hpEsPortResetTimer	TimeTicks,
	hpEsPortResetAddrs	INTEGER,
	hpEsPortRcvBcasts	Counter,
	hpEsPortSwitchedFrames  Counter
	}

hpEsPortIndex OBJECT-TYPE
	SYNTAX	INTEGER (1..65535)
	ACCESS	read-only
	STATUS	mandatory
	DESCRIPTION
		"A unique value for each port entry.  The value
		corresponds the port number."
	::= { hpEsPortEntry 1 }

hpEsPortOprStatus OBJECT-TYPE
	SYNTAX	INTEGER {
		enabled(1),	-- port enabled
		disabled(2)	-- port disabled
		}
	ACCESS	read-write
	STATUS	mandatory
	DESCRIPTION
		"The operational status of the port.  Setting to
		enabled(1) enables the port.  Setting to
		disabled(2) disables the port.  The value is saved across
		resets and power cycles."
	::= { hpEsPortEntry 2 }

hpEsPortExtConn OBJECT-TYPE
	SYNTAX	INTEGER {
		other(1),
		aui(2),
		rj45(3),
		noExternal(4)
		}
	ACCESS	read-only
	STATUS	mandatory
	DESCRIPTION
		"Which external connector has been configured via
		jumpers.  For EPS1500, this object will always
		return AUI."
	::= { hpEsPortEntry 5 }

hpEsPortDuplex OBJECT-TYPE
	SYNTAX	INTEGER {
		fullDuplex(1),
		halfDuplex(2)
		}
	ACCESS	read-only
	STATUS	mandatory
	DESCRIPTION
		"Indicates whether the port is jumper configured
		for full or half duplex operation.  Note:
		internal connected ports are always
		halfDuplex(2)."
	::= { hpEsPortEntry 6 }

hpEsPortRcvLocalFrames OBJECT-TYPE
	SYNTAX	Counter
	ACCESS	read-only
	STATUS	mandatory
	DESCRIPTION
		"Number of frames received where the destination
		is on this port."
	::= { hpEsPortEntry 7 }

hpEsPortForwardedFrames OBJECT-TYPE
	SYNTAX	Counter
	ACCESS	read-only
	STATUS	mandatory
	DESCRIPTION
		"Number of frames received on this port and
		forwarded to another port."
	::= { hpEsPortEntry 8 }

hpEsPortMostStations OBJECT-TYPE
	SYNTAX	Counter
	ACCESS	read-only
	STATUS	mandatory
	DESCRIPTION
		"Highest number of stations ever active at any
		time since the last reset of the switch as seen by
		this port."
	::= { hpEsPortEntry 10 }

hpEsPortMaxStations OBJECT-TYPE
	SYNTAX	Counter
	ACCESS	read-only
	STATUS	mandatory
	DESCRIPTION
		"Maximum number of stations which the port can
		support simultaneously."
	::= { hpEsPortEntry 11 }

hpEsPortSWHandledFrames OBJECT-TYPE
	SYNTAX	Counter
	ACCESS	read-only
	STATUS	mandatory
	DESCRIPTION
		"Number of Frames received on this port and
		delivered to the system module for processing."
	::= { hpEsPortEntry 12 }

hpEsPortLocalStations OBJECT-TYPE
	SYNTAX	Counter
	ACCESS	read-only
	STATUS	mandatory
	DESCRIPTION
		"Number of stations on this port which belong to
		the local segment."
	::= { hpEsPortEntry 13 }

hpEsPortRemoteStations OBJECT-TYPE
	SYNTAX	Counter
	ACCESS	read-only
	STATUS	mandatory
	DESCRIPTION
		"Number of stations on this port which belong to
		another segment."
	::= { hpEsPortEntry 14 }

hpEsPortUnknownStaFrames OBJECT-TYPE
	SYNTAX	Counter
	ACCESS	read-only
	STATUS	mandatory
	DESCRIPTION
		"Number of unicast frames received on this port
		and forwarded to the system module for processing
		because the source or destination station address 
		is not in the port's forwarding table."
	::= { hpEsPortEntry 15 }

hpEsPortResetStats OBJECT-TYPE
	SYNTAX	INTEGER {
		other(1),	-- none of the following
		running(2),	-- port is functioning
		reset(3)	-- reset port counters
		}
	ACCESS	read-write
	STATUS	mandatory
	DESCRIPTION
		"Setting this object to reset(3) causes all
		traffic counters for this port to be set to zero.
		Also the value of hpEsPortResetTimer is set to
		zero."
	::= { hpEsPortEntry 16 }

hpEsPortResetTimer OBJECT-TYPE
	SYNTAX	TimeTicks
	ACCESS	read-only
	STATUS	mandatory
	DESCRIPTION
		"Time (in 100th second ticks) since the port
		counters were reset."
	::= { hpEsPortEntry 17 }


hpEsPortResetAddrs OBJECT-TYPE
	SYNTAX	INTEGER {
		other(1),	-- none of the following
		running(2),	-- port is functioning
		reset(3)	-- clear address table &
		}		--  reset port counters
	ACCESS	read-write
	STATUS	mandatory
	DESCRIPTION
		"Setting this object to reset(3) clears all
		address table entries for this port as well as
		setting all port traffic counters to zero and
		setting hpEsPortResetTimer to zero."
	::= { hpEsPortEntry 18 }

hpEsPortRcvBcasts OBJECT-TYPE
	SYNTAX	Counter
	ACCESS	read-only
	STATUS	mandatory
	DESCRIPTION
		"Number of Broadcast Frames received on this port
		without errors."
	::= { hpEsPortEntry 20 }

hpEsPortSwitchedFrames OBJECT-TYPE
	SYNTAX	Counter
	ACCESS	read-only
	STATUS	mandatory
	DESCRIPTION
		"Number of frames switched on this port"
	::= { hpEsPortEntry 25 }


END
